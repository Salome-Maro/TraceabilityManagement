# Specification: Specification Document
- Description: Requirements Document

## R1
When the On button is pressed, the light shold turn On

## R2
When the Off button is pressed, the light should turn Off
